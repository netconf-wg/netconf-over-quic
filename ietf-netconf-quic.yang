module ietf-netconf-quic {
  yang-version 1.1;
  namespace
    "urn:ietf:params:xml:ns:yang:ietf-netconf-quic";
  prefix ncquic;

  import ietf-netconf-client {
    prefix ncc;
    reference
      "RFC BBBB: NETCONF Client and Server Models";
  }

  import ietf-netconf-server {
    prefix ncs;
    reference
      "RFC BBBB: NETCONF Client and Server Models";
  }

  import ietf-quic-client {
    prefix quicc;
    reference
      "RFC CCCC: YANG Groupings for QUIC Clients and QUIC Servers";
  }

  import ietf-quic-server {
    prefix quics;
    reference
      "RFC CCCC: YANG Groupings for QUIC Clients and QUIC Servers";
  }

  import ietf-yang-semver {
    prefix ysv;
    reference
      "draft-ietf-netmod-yang-semver: YANG Semantic Versioning";
  }

  organization
    "IETF NETCONF (Network Configuration) Working Group";

  contact
    "WG Web:  https://datatracker.ietf.org/wg/netconf
     WG List: NETCONF WG list <mailto:netconf@ietf.org>

     Author:  Jinyou Dai
              <mailto:djy@fiberhome.se>

     Author:  Shaohua Yu
              <mailto:yush@cae.cn>

     Author:  Weiqiang Cheng
              <mailto:chengeiqiang@chinamobile.com>

     Author:  Marc Blanchet
              <mailto:marc.blanchet@viagenie.ca>

     Author:  Per Andersson
              <mailto:per.ietf@ionio.se>";

  description
    "This module defines augmentations for a NETCONF server to
     also support the QUIC transport.

     Copyright (c) 2025 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC AAAA
     (https://www.rfc-editor.org/info/rfcAAAA); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision YYYY-MM-DD {
    ysv:version 1.0.0-draft-ietf-netconf-over-quic-latest;
    description
      "Initial version";
    reference
      "RFC AAAA: NETCONF over QUIC";
  }

  // Features

  feature quic-initiate {
    description
      "The 'quic-initiate' feature indicates that the NETCONF client
       supports initiating QUIC connections to NETCONF servers.";
    reference
      "RFC CCCC: YANG Groupings for QUIC Clients and QUIC Servers";
  }

  feature quic-listen {
    description
      "The 'quic-listen' feature indicates that the NETCONF server
       supports the QUIC transport.";
    reference
      "RFC AAAA: NETCONF over QUIC";
  }

  // Augments

  augment "/ncc:netconf-client/ncc:initiate" {
    if-feature "quic-initiate";
    description
      "Add 'quic-initate' feature to the NETCONF client connection
       configuration.";
  }

  augment "/ncc:netconf-client/ncc:initiate/ncc:netconf-server" +
          "/ncc:endpoints/ncc:endpoint/ncc:transport" {
    description
      "Add QUIC transport to the NETCONF client connection
       configuration";
    case quic {
      if-feature "quic-initiate";
      container quic {
        description
          "QUIC-level client parameters to initiate a NETCONF over
           QUIC connection.";
        uses quicc:quic-client;
      }
    }
  }

  augment "/ncs:netconf-server/ncs:listen" {
    if-feature "quic-listen";
    description
      "Add 'quic-listen' feature to the NETCONF server listen
       configuration.";
  }

  augment "/ncs:netconf-server/ncs:listen/ncs:endpoints" +
          "/ncs:endpoint/ncs:transport" {
    description
      "Add QUIC transport to the NETCONF server listen
       configuration.";
    case quic {
      if-feature "quic-listen";
      container quic {
        description
          "QUIC-level server parameters to listen for NETCONF over
           QUIC connections.";
        uses quics:quic-server;
      }
    }
  }
}
