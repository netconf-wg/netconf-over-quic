module ietf-quic-client {
  yang-version 1.1;
  namespace
    "urn:ietf:params:xml:ns:yang:ietf-quic-client";
  prefix quicc;

  import ietf-quic-common {
    prefix quiccmn;
    reference
      "RFC AAAA: YANG Groupings for QUIC Clients and QUIC Servers";
  }

  import ietf-tls-client {
    prefix tlsc;
    reference
      "RFC 9645: YANG Groupings for TLS Clients and TLS Servers";
  }

  import ietf-tls-common {
    prefix tlscmn;
    reference
      "RFC 9645: YANG Groupings for TLS Clients and TLS Servers";
  }

  import ietf-udp-client {
    prefix udpc;
    reference
      "RFC CCCC: YANG Groupings for UDP Clients and UDP Servers";
  }

  organization
    "IETF NETCONF (Network Configuration) Working Group";

  contact
    "WG List: NETCONF WG list <mailto:netconf@ietf.org>
     WG Web:  https://datatracker.ietf.org/wg/netconf
     Author:  Per Andersson <mailto:per.ietf@ionio.se>";

  description
    "This module defines reusable groupings for QUIC clients that
     can be used as a basis for specific QUIC client instances.

     Copyright (c) 2024 IETF Trust and the persons identified
     as authors of the code. All rights reserved.

     Redistribution and use in source and binary forms, with
     or without modification, is permitted pursuant to, and
     subject to the license terms contained in, the Revised
     BSD License set forth in Section 4.c of the IETF Trust's
     Legal Provisions Relating to IETF Documents
     (https://trustee.ietf.org/license-info).

     This version of this YANG module is part of RFC AAAA
     (https://www.rfc-editor.org/info/rfcAAAA); see the RFC
     itself for full legal notices.

     The key words 'MUST', 'MUST NOT', 'REQUIRED', 'SHALL',
     'SHALL NOT', 'SHOULD', 'SHOULD NOT', 'RECOMMENDED',
     'NOT RECOMMENDED', 'MAY', and 'OPTIONAL' in this document
     are to be interpreted as described in BCP 14 (RFC 2119)
     (RFC 8174) when, and only when, they appear in all
     capitals, as shown here.";

  revision 2025-10-17 {
    description
      "Initial version";
    reference
      "RFC AAAA: YANG Groupings for QUIC Clients and QUIC Servers";
  }

  // Groupings

  grouping quic-client {
    description
      "Grouping to configure a QUIC client.";
    reference
      "RFC 9000: QUIC: A UDP-Based Multiplexed and Secure Transport";

    uses tlsc:tls-client-grouping {
      if-feature "tlscmn:tls13 and not tlscmn:tls12";
      description
        "QUIC requires that TLS 1.3 (or later) is used.";
      reference
        "RFC 9001: Using TLS to Secure QUIC";
    }
    uses udpc:udp-client;
    uses quiccmn:transport-parameters;
  }
}
